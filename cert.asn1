Nebula DEFINITIONS AUTOMATIC TAGS ::= BEGIN

Signature ::= OCTET STRING (SIZE (32))
Time ::= INTEGER (0..99999999999)
Ip ::= INTEGER (0..18446744073709551615)

Certificate ::= SEQUENCE {
	details CertificateDetails,
	signature Signature
}

CertificateDetails ::= SEQUENCE {
	name UTF8String (SIZE (1..253)),

	ip IPNet,
	subnets SEQUENCE SIZE(0..1024) OF IPNet OPTIONAL,
	groups SEQUENCE SIZE(0..1024) OF UTF8String (SIZE(0..1024)) OPTIONAL,

	-- ASN.1 time formats are all string representations
	notBefore Time,
	notAfter Time,

	publicKey OCTET STRING (SIZE (32)),
	issuer OCTET STRING (SIZE (32)),
	...
}

IPNet ::= SEQUENCE {
    hi Ip OPTIONAL,
    lo Ip,
	suffix INTEGER (0..128)
}

END
